(defun C:LEAF()
  (graphscr)

  (setvar "fillmode" 1)
  (setvar "cmdecho" 0)
  (prompt "\nLungimea frunzei este cota orizontala...")
  (setq le (getreal "\nIntroduceti lungimea frunzei:"))
  (setq p1 (getpoint "\nIntroduceti punctul central: "))
  (setq a (- 0 (/ pi 6)))
  (repeat 5
	(setq mle (+ le (* le (sin a))))
 	(setq p2 (polar p1 a mle))
	(setq p3 (polar p1 a (/ mle 2)))
	(setq p4 (polar p3 (+ a (/ pi 2)) (* 0.134 mle)))
	(setq th (* 0.07 mle))
	(command "pline" p1 "w" 0 th "a" "a" -30 p4 "w" th 0 "a" -30 p2 "")
	(command "mirror" p2 "" p1 p2 "")
	(setq a (+ a (/ pi 6)))
  )
  (setq p5 (polar p1 (* 7 (/ pi 6)) le))
  (setq p6 (polar p1 (/ pi 4) (* 1.4 mle)))
  (command "mirror" "c" p5 p6 "" p1 p2 "")
  (princ)
  (setvar "cmdecho" 1)
)
